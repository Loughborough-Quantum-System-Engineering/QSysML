// reference
// @article{lekitsch2017blueprint,
//   title={Blueprint for a microwave trapped ion quantum computer},
//   author={Lekitsch, Bjoern and Weidt, Sebastian and Fowler, Austin G and M{\o}lmer, Klaus and Devitt, Simon J and Wunderlich, Christof and Hensinger, Winfried K},
//   journal={Science Advances},
//   volume={3},
//   number={2},
//   pages={e1601540},
//   year={2017},
//   publisher={American Association for the Advancement of Science}
// }
//
// Provenance notation used in line comments:
//   [p.N LC]  = page N, left  column   (para k = k-th paragraph of that column)
//   [p.N RC]  = page N, right column
//   [Fig.1A]  = Fig. 1A X-junction with multiple zones, p.3
//   [Fig.2A]  = Fig. 2A gradient wires under the gate zone, p.4
//   [Fig.2B]  = Fig. 2B embedded silicon photodetector, p.4

package MicrowaveTrappedIonInterface {

    doc
    /*
     * Microwave-driven control and readout interface for a trapped ion
     * quantum computer module, based on long-wavelength radiation and static
     * magnetic field gradients rather than individually addressed laser
     * beams.
     *
     * Coupling between the internal states of trapped ions and their motion
     * is vanishingly small for free-running microwaves because of the
     * centimetre wavelength, and so is not useful on its own for multiqubit
     * gates. Adding a static magnetic field gradient exerts a force on the
     * magnetic moment associated with the qubit states, which makes
     * multiqubit gates possible. The correlation between the number of ions
     * and the number of required gate radiation fields then vanishes, so
     * that instead of thousands or millions of individually controllable
     * fields, only a handful of global microwave fields are needed,
     * independent of the number of ions.
     *
     * Each X-junction features up to three zones: a microwave gate zone, a
     * state readout zone, and a loading zone. Laser light is required only
     * for state preparation and detection, photoionization, and sympathetic
     * cooling, and those beams need be neither intense nor phase-stable.
     *
     * Source: Lekitsch et al. 2017, p.2 right column through p.5 right
     * column, with Figs. 1 and 2.
     *
     * Units: prefixed unit symbols are not recognised, so quantities are
     * expressed in SI base units with a scaled literal, and the value as
     * printed in the reference is restated in the documentation of the
     * owning element.
     */

    public import QuantumComputing::physicalLayerDefinitions::*;
    public import CommonInstruments::*;
    public import AtomicCommon::*;
    public import ISQ::*;
    public import SI::*;

    // =====================================================================
    // Action definitions
    // =====================================================================

    action def PerformQuantumGate {
        doc
        /*
         * Perform single- and multiqubit gates in the gate zone. The gate
         * zones perform all quantum operations, controlled by in-vacuum
         * electronics and powered by the global long-wavelength radiation
         * fields, with the ions individually addressed by the locally
         * adjustable magnetic fields and entangled using the static gradient
         * in conjunction with the global microwave and rf fields.
         *
         * Source: p.4, right column, paragraph 1; p.2, right column,
         * paragraph 3.
         */
        in item globalField : microwaveSignal;
        in item gradient : magneticField;
        in item offsetField : magneticField;
        in item electrodePotential : dcBias;
        in item trapDrive : microwaveSignal;
        out item fluorescence : opticalSignal;
    }

    action def PrepareState {
        doc
        /*
         * Prepare the initial internal state of the ion using laser light.
         *
         * Source: p.2, right column, paragraph 3.
         */
        in item statePrepBeam : opticalSignal;
    }

    action def RemoveHeat {
        doc
        /*
         * Remove the heat generated by the copper wires, rf dissipation in
         * the trap structure and the on-chip electronics. A liquid nitrogen
         * microchannel cooler is integrated into the back wafer of the
         * module; deep trenches are etched into the backside of the last
         * wafer, forming channels through which liquid nitrogen is passed.
         * The coolant is cooled from 77 K to 65 K to prevent boiling inside
         * the cooler. Cooling the silicon substrates below 100 K also raises
         * the thermal conductivity of silicon sharply and of copper by a
         * factor of ten, which prevents the wire structures from melting.
         *
         * Source: p.5, left column, paragraphs 3 and 4.
         */
        attribute heatOutputPerModule = 1.0E3 [W];  // ~1000 W [p.5 LC para 3]
        attribute powerDensity;                     // 0.12 W/mm2 [p.5 LC para 3]
    }

    action def ApplyElectrodeVoltage :> ConditionSignal {
        doc
        /* Summing amplification circuit applying the highly stable electrode
         * potentials, overridden by the fast control system during shuttling.
         * Kept local because the library SupplyBias is a pure source, whereas
         * this stage conditions an incoming voltage.
         *
         * Source: p.4, right column, paragraph 2.
         */
        in item electrodeIn : dcBias;
        out item electrodePotential : dcBias;
        attribute voltageStability;
    }
    action def ConvertToAnalogDrive :> ConvertSignal {
        doc
        /* In-vacuum converters producing both the coil currents and the
         * electrode voltages. Kept local because it has two distinct analog
         * outputs, unlike the single-output library converter.
         *
         * Source: p.4 right column paragraph 1; p.5 right column paragraph 1.
         */
        in item command : digitalData;
        out item coilCurrent : dcBias;
        out item electrodeVoltage : dcBias;
        attribute precision;
        attribute updateRate : FrequencyValue;
    }

    // =====================================================================
    // End-to-end behaviour
    // =====================================================================
    action def MicrowaveTrappedIonControlAndReadout {

        doc
        /*
         * Sequence of the microwave trapped ion control and readout cycle.
         *
         * An ion is loaded and cooled, prepared, and shuttled to the gate
         * zone. There the global microwave field, the static gradient, the
         * local offset field and the electrode potentials combine to perform
         * the gate. The ion is then shuttled to the readout zone, where the
         * steered laser beams excite it, the emitted light passes through the
         * transparent electrodes to the embedded photon counter, and the
         * count is converted to a state.
         *
         * The gradient is turned off during shuttling, which is why the
         * gradient generation and the shuttling steps are ordered rather than
         * concurrent.
         *
         * This definition states ordering and the action-to-action item
         * chain. The physical routing of those items through ports is
         * modelled in the parts.
         *
         * Source: p.2 right column paragraph 3 through p.5 right column
         * paragraph 1, with Figs. 1 and 2.
         */

        out item measuredQubitState : digitalData;

        // ---- room-temperature generation ----
        action generateGlobalMicrowaveField : GenerateMicrowaveDrive;  // [p.4 RC para 1]
        action amplifyMicrowave : Amplify;                // [p.4 RC para 1]
        action radiateGlobalField : RadiateBeam;            // [p.4 LC para 2]
        action generateRfTrapDrive : GenerateTrapDrive;          // [p.5 RC para 1]
        action resonateRfDrive : Resonate;                  // [p.5 RC para 1]
        action issueControlCommand : IssueCommand;          // [p.5 RC para 1]
        action generateIonisationBeam : GenerateLaserBeam;         // [p.2 RC para 3]
        action generateCoolingBeam : GenerateLaserBeam;            // [p.2 RC para 3]
        action generateStatePrepBeam : GenerateLaserBeam;          // [p.2 RC para 3]
        action generateSympatheticBeam : GenerateLaserBeam;        // [p.2 RC para 3]
        action steerLaserBeam : SteerBeam;                    // [p.5 LC para 2]
        action generateReadoutExcitation : GenerateLaserBeam;      // [p.5 LC para 2]

        // ---- in-vacuum electronics ----
        action convertToAnalogDrive : ConvertToAnalogDrive;        // [p.4 RC para 1]
        action filterElectrodeVoltage : FilterSignal;    // [p.5 RC para 1]
        action generateFieldGradient : GenerateFieldGradient;      // [p.4 LC para 1]
        action adjustLocalMagneticField : AdjustLocalMagneticField;// [p.4 LC para 4]
        action applyElectrodeVoltage : ApplyElectrodeVoltage;      // [p.4 RC para 2]
        action removeHeat : RemoveHeat;                            // [p.5 LC para 4]

        // ---- ion operations ----
        action loadIon : LoadIon;                                  // [p.3 RC para 2]
        action coolIon : CoolAtom;                                  // [p.2 RC para 3]
        action prepareState : PrepareState;                        // [p.2 RC para 3]
        action shuttleToGateZone : TransportIon;                     // [p.3 LC para 1]
        action performQuantumGate : PerformQuantumGate;            // [p.4 RC para 1]
        action shuttleToReadoutZone : TransportIon;                  // [p.3 LC para 1]

        // ---- readout ----
        action transmitFluorescence : CollectLight;        // [p.4 RC para 4]
        action countPhotons : DetectPhotons;                        // [p.4 RC para 4]
        action determineQubitState : EvaluateMeasurement;          // [p.5 LC para 1]
        action analyseResult : AnalyseMeasurement;                      // [p.5 RC para 1]

        // ---- control nodes ----
        fork initiate;
        join joinGate;

        // ---- ordering ----
        first start then initiate;

        // trapping field and cooling loop are established and held
        first initiate then generateRfTrapDrive;                   // [p.5 RC para 1]
        first generateRfTrapDrive then resonateRfDrive;
        first initiate then removeHeat;                            // [p.5 LC para 4]

        // global microwave chain
        first initiate then generateGlobalMicrowaveField;          // [p.4 RC para 1]
        first generateGlobalMicrowaveField then amplifyMicrowave;
        first amplifyMicrowave then radiateGlobalField;

        // laser generation and steering
        first initiate then generateIonisationBeam;                // [p.2 RC para 3]
        first initiate then generateCoolingBeam;
        first initiate then generateStatePrepBeam;
        first initiate then generateSympatheticBeam;
        first initiate then generateReadoutExcitation;
        first generateIonisationBeam then steerLaserBeam;          // [p.5 LC para 2]

        // digital command chain into the in-vacuum converters
        first initiate then issueControlCommand;                   // [p.5 RC para 1]
        first issueControlCommand then convertToAnalogDrive;
        first convertToAnalogDrive then filterElectrodeVoltage;
        first filterElectrodeVoltage then applyElectrodeVoltage;   // [p.4 RC para 2]
        first convertToAnalogDrive then adjustLocalMagneticField;  // [p.4 LC para 4]

        // ion preparation
        first steerLaserBeam then loadIon;                         // [p.3 RC para 2]
        first loadIon then coolIon;                                // [p.2 RC para 3]
        first coolIon then prepareState;

        // shuttle with the gradient off, then raise it for the gate
        first prepareState then shuttleToGateZone;                 // [p.3 LC para 2]
        first applyElectrodeVoltage then shuttleToGateZone;
        first shuttleToGateZone then generateFieldGradient;        // [p.4 RC para 3]
        first generateFieldGradient then joinGate;
        first radiateGlobalField then joinGate;
        first adjustLocalMagneticField then joinGate;
        first resonateRfDrive then joinGate;
        first joinGate then performQuantumGate;                    // [p.4 RC para 1]

        // shuttle to the readout zone and detect
        first performQuantumGate then shuttleToReadoutZone;        // [p.3 LC para 1]
        first shuttleToReadoutZone then transmitFluorescence;      // [p.4 RC para 4]
        first transmitFluorescence then countPhotons;
        first countPhotons then determineQubitState;               // [p.5 LC para 1]
        first determineQubitState then analyseResult;
        first analyseResult then done;

        // ---- item chain ----
        flow from generateGlobalMicrowaveField.drive to amplifyMicrowave.weakSignal;
        flow from amplifyMicrowave.amplifiedSignal to radiateGlobalField.feed;
        flow from radiateGlobalField.beam to performQuantumGate.globalField;
        flow from generateRfTrapDrive.rfDrive to resonateRfDrive.input;
        flow from resonateRfDrive.output to performQuantumGate.trapDrive;

        flow from issueControlCommand.command to convertToAnalogDrive.command;
        flow from convertToAnalogDrive.electrodeVoltage to filterElectrodeVoltage.unfiltered;
        flow from filterElectrodeVoltage.filtered to applyElectrodeVoltage.electrodeIn;
        flow from convertToAnalogDrive.coilCurrent to generateFieldGradient.current;
        flow from convertToAnalogDrive.coilCurrent to adjustLocalMagneticField.current;
        flow from generateFieldGradient.gradient to performQuantumGate.gradient;
        flow from adjustLocalMagneticField.offsetField to performQuantumGate.offsetField;
        flow from applyElectrodeVoltage.electrodePotential to performQuantumGate.electrodePotential;
        flow from applyElectrodeVoltage.electrodePotential to shuttleToGateZone.electrodePotential;
        flow from applyElectrodeVoltage.electrodePotential to shuttleToReadoutZone.electrodePotential;

        flow from generateIonisationBeam.beam to steerLaserBeam.beam;
        flow from steerLaserBeam.steeredBeam to loadIon.ionisationBeam;
        flow from generateCoolingBeam.beam to coolIon.coolingBeam;
        flow from generateSympatheticBeam.beam to coolIon.coolingBeam;
        flow from generateStatePrepBeam.beam to prepareState.statePrepBeam;

        flow from performQuantumGate.fluorescence to transmitFluorescence.emittedLight;
        flow from generateReadoutExcitation.beam to steerLaserBeam.beam;
        flow from transmitFluorescence.collectedLight to countPhotons.light;
        flow from countPhotons.count to determineQubitState.measurement;
        flow from determineQubitState.result to analyseResult.measurement;

        bind measuredQubitState = analyseResult.qubitState;
    }

    action microwaveOperation : MicrowaveTrappedIonControlAndReadout;

    // =====================================================================
    // Structure
    // =====================================================================
    part microwaveControlSystem : classicalControlSystem {

        doc
        /*
         * Control instrumentation outside the vacuum system: the global
         * microwave chain, the rf trap drive and its resonator, the digital
         * control unit, and the laser system whose beams are steered into the
         * chamber.
         *
         * Source: p.4 right column paragraph 1; p.5 right column
         * paragraph 1; p.2 right column paragraph 3.
         */

        part globalFrequencyGenerator : microwaveSource {
            doc
            /*
             * Commercial frequency generator producing the global field
             * frequencies.
             *
             * Source: p.4, right column, paragraph 1.
             */
            port toneOut : microwavePort {
                in item item1;
            }
            perform microwaveOperation.generateGlobalMicrowaveField;
            flow from generateGlobalMicrowaveField.drive to toneOut.item1;
        }
        part microwaveAmplifier {
            port ampIn : ~microwavePort {
                out item item1;
            }
            port ampOut : microwavePort {
                in item item1;
            }
            perform microwaveOperation.amplifyMicrowave;           // [p.4 RC para 1]
            flow from ampIn.item1 to amplifyMicrowave.weakSignal;
            flow from amplifyMicrowave.amplifiedSignal to ampOut.item1;
        }
        part radiationEmitter {
            doc
            /*
             * Emitter placed periodically within the vacuum chamber,
             * radiating one of the handful of global long-wavelength fields.
             *
             * Source: p.4, left column, paragraph 2.
             */
            port feedIn : ~microwavePort {
                out item item1;
            }
            port globalFieldOut : microwavePort {
                in item item1;
            }
            perform microwaveOperation.radiateGlobalField;
            flow from feedIn.item1 to radiateGlobalField.feed;
            flow from radiateGlobalField.beam to globalFieldOut.item1;
        }
        part rfFrequencySource {
            port rfOut : microwavePort {
                in item item1;
            }
            perform microwaveOperation.generateRfTrapDrive;        // [p.5 RC para 1]
            flow from generateRfTrapDrive.rfDrive to rfOut.item1;
        }
        part helicalResonator {
            doc
            /*
             * Compact helical resonator, around 15 mm in diameter, tuned into
             * resonance with the frequency source using a tuning capacitor.
             * All resonators are attached to the same frequency source.
             *
             * Source: p.5, right column, paragraph 1.
             */
            part variableCapacitor;
            port rfIn : ~microwavePort {
                out item item1;
            }
            port rfOut : microwavePort {
                in item item1;
            }
            perform microwaveOperation.resonateRfDrive;
            flow from rfIn.item1 to resonateRfDrive.input;
            flow from resonateRfDrive.output to rfOut.item1;
        }
        part digitalController {
            doc
            /*
             * Electronic control unit housed on an additional wafer layer,
             * controlling the in-vacuum converters and the detection system.
             *
             * Source: p.5, right column, paragraph 1.
             */
            port controlOut : digitalPort {
                in item item1;
            }
            perform microwaveOperation.issueControlCommand;
            flow from issueControlCommand.command to controlOut.item1;
        }
        part globalLaserSystem {
            doc
            /*
             * Laser system supplying the beams required for photoionization,
             * Doppler and sympathetic cooling, and state preparation. These
             * beams need be neither intense nor phase-stable.
             *
             * Source: p.2, right column, paragraph 3.
             */
            part photoionisationLaser {
                port beamOut : opticalPort {
                    in item item1;
                }
                perform microwaveOperation.generateIonisationBeam;
                flow from generateIonisationBeam.beam to beamOut.item1;
            }
            part dopplerCoolingLaser {
                port beamOut : opticalPort {
                    in item item1;
                }
                perform microwaveOperation.generateCoolingBeam;
                flow from generateCoolingBeam.beam to beamOut.item1;
            }
            part statePreparationLaser {
                port beamOut : opticalPort {
                    in item item1;
                }
                perform microwaveOperation.generateStatePrepBeam;
                flow from generateStatePrepBeam.beam to beamOut.item1;
            }
            part sympatheticCoolingLaser {
                port beamOut : opticalPort {
                    in item item1;
                }
                perform microwaveOperation.generateSympatheticBeam;
                flow from generateSympatheticBeam.beam to beamOut.item1;
            }
            part inVacuumBeamSteeringOptics {
                doc
                /*
                 * In-vacuum optics steering the global beams parallel to and
                 * between the gate zone arms, so that only ions in the
                 * readout zones are illuminated.
                 *
                 * Source: p.5, left column, paragraph 2.
                 */
                port photoionisationIn : ~opticalPort {
                    out item item1;
                }
                port coolingIn : ~opticalPort;
                port statePrepIn : ~opticalPort;
                port sympatheticIn : ~opticalPort;
                port sheetOut : opticalPort {
                    in item item1;
                }
                perform microwaveOperation.steerLaserBeam;
                flow from photoionisationIn.item1 to steerLaserBeam.beam;
                flow from steerLaserBeam.steeredBeam to sheetOut.item1;
            }
            port laserSheetOut : opticalPort;
            flow from photoionisationLaser.beamOut to inVacuumBeamSteeringOptics.photoionisationIn;
            flow from dopplerCoolingLaser.beamOut to inVacuumBeamSteeringOptics.coolingIn;
            flow from statePreparationLaser.beamOut to inVacuumBeamSteeringOptics.statePrepIn;
            flow from sympatheticCoolingLaser.beamOut to inVacuumBeamSteeringOptics.sympatheticIn;
            flow from inVacuumBeamSteeringOptics.sheetOut to laserSheetOut;
        }
        port globalMicrowaveOut : microwavePort;
        port rfTrapDriveOut : microwavePort;
        port laserSheetOut : opticalPort;
        port digitalControlOut : digitalPort;
        flow from globalFrequencyGenerator.toneOut to microwaveAmplifier.ampIn;
        flow from microwaveAmplifier.ampOut to radiationEmitter.feedIn;
        flow from radiationEmitter.globalFieldOut to globalMicrowaveOut;
        flow from rfFrequencySource.output to helicalResonator.input;
        flow from helicalResonator.output to rfTrapDriveOut;
        flow from globalLaserSystem.laserSheetOut to laserSheetOut;
        flow from digitalController.controlOut to digitalControlOut;
    }

    part vacuumChamberEnv {

        doc
        /*
         * Ultrahigh vacuum chamber housing the quantum computer module. The
         * chambers are octagon shaped, about 4.5 by 4.5 m, with viewports on
         * the sides and top for optical access, and carry the feedthroughs
         * for currents, static voltages, rf and microwave signals, coolant
         * and digital control signals.
         *
         * Source: p.7, left column, paragraph 2.
         */

        attribute pressure : PressureUnit;

        port globalMicrowaveIn : ~microwavePort;
        port rfTrapDriveIn : ~microwavePort;
        port laserSheetIn : ~opticalPort;
        port digitalControlIn : ~digitalPort;
        port readoutExcitationIn : ~opticalPort;
        port photonCountOut : digitalPort;

        part viewport {
            port beamIn : ~opticalPort;
            port beamOut : opticalPort;
        }
        part readoutViewport {
            port beamIn : ~opticalPort;
            port beamOut : opticalPort;
        }
        part vacuumPump;
        part liquidNitrogenHeatShield;
        part electricalFeedthrough {
            port signalIn : ~digitalPort;
            port signalOut : digitalPort;
        }
        part steelFrame;

        part quantumComputerModule {
            doc
            /*
             * Scalable quantum computer module, 6 by 6 electrical submodules
             * on a 90 by 90 mm high-resistivity silicon wafer piece,
             * containing 1296 X-junctions. The module is controlled by
             * on-chip electronics and performs the required quantum
             * operations using magnetic field gradients, local magnetic
             * fields, and global laser and microwave fields.
             *
             * Source: p.5, right column, paragraph 2.
             */
            attribute temp : ThermodynamicTemperatureUnit = 72 [K];

            part qpu : QPU {
                doc
                /*
                 * The X-junction array holding the ions, with its gate,
                 * readout and loading zones. Modelled as a black box so that
                 * only the classical interface is in scope; the gate zones
                 * perform all quantum operations, controlled by the in-vacuum
                 * electronics and powered by the global radiation fields.
                 *
                 * Source: p.4 right column paragraph 1; p.2 right column
                 * paragraph 3; Fig. 1A.
                 */
                attribute redefines technology = qubitTechnology::trappedIon;
                port globalMicrowaveIn : ~microwavePort {
                    out item item1;
                }
                port rfTrapIn : ~microwavePort {
                    out item item1;
                }
                port gradientIn : ~magneticFieldPort {
                    out item item1;
                }
                port offsetFieldIn : ~magneticFieldPort {
                    out item item1;
                }
                port electrodeVoltageIn : ~dcBiasPort {
                    out item item1;
                }
                port laserSheetIn : ~opticalPort {
                    out item item1;
                }
                port readoutExcitationIn : ~opticalPort;
                port fluorescenceOut : opticalPort {
                    in item item1;
                }
                perform microwaveOperation.loadIon;
                perform microwaveOperation.coolIon;
                perform microwaveOperation.prepareState;
                perform microwaveOperation.shuttleToGateZone;
                perform microwaveOperation.performQuantumGate;
                perform microwaveOperation.shuttleToReadoutZone;
                flow from globalMicrowaveIn.item1 to performQuantumGate.globalField;
                flow from rfTrapIn.item1 to performQuantumGate.trapDrive;
                flow from gradientIn.item1 to performQuantumGate.gradient;
                flow from offsetFieldIn.item1 to performQuantumGate.offsetField;
                flow from electrodeVoltageIn.item1 to performQuantumGate.electrodePotential;
                flow from electrodeVoltageIn.item1 to shuttleToGateZone.electrodePotential;
                flow from electrodeVoltageIn.item1 to shuttleToReadoutZone.electrodePotential;
                flow from laserSheetIn.item1 to loadIon.ionisationBeam;
                flow from laserSheetIn.item1 to coolIon.coolingBeam;
                flow from laserSheetIn.item1 to prepareState.statePrepBeam;
                flow from performQuantumGate.fluorescence to fluorescenceOut.item1;
            }
            part gradientWire {
                doc
                /*
                 * Copper wire embedded in the silicon substrate, carrying
                 * about 10 A to generate the static magnetic field gradient
                 * at the ion position.
                 *
                 * Source: p.4, left column, paragraph 1; Fig. 2A.
                 */
                port currentIn : ~dcBiasPort {
                    out item item1;
                }
                port gradientOut : magneticFieldPort {
                    in item item1;
                }
                perform microwaveOperation.generateFieldGradient;
                flow from currentIn.item1 to generateFieldGradient.current;
                flow from generateFieldGradient.gradient to gradientOut.item1;
            }
            part localBFieldCoil {
                doc
                /*
                 * Very low inductance coil placed underneath each gate zone,
                 * used to shift the qubit in and out of resonance with the
                 * global radiation fields and to compensate slow variations
                 * of the global magnetic field.
                 *
                 * Source: p.4, left column, paragraph 4; p.4, right column,
                 * paragraph 1; Fig. 2A.
                 */
                port currentIn : ~dcBiasPort {
                    out item item1;
                }
                port offsetFieldOut : magneticFieldPort {
                    in item item1;
                }
                perform microwaveOperation.adjustLocalMagneticField;
                flow from currentIn.item1 to adjustLocalMagneticField.current;
                flow from adjustLocalMagneticField.offsetField to offsetFieldOut.item1;
            }
            part itoElectrode {
                doc
                /*
                 * Indium tin oxide centre segmented electrode in the readout
                 * zone, ultraviolet transparent so that light emitted by the
                 * ion passes through to the detector below.
                 *
                 * Source: p.4, right column, paragraph 4; Fig. 2B.
                 */
                port photonIn : ~opticalPort {
                    out item item1;
                }
                port photonOut : opticalPort {
                    in item item1;
                }
                perform microwaveOperation.transmitFluorescence;
                flow from photonIn.item1 to transmitFluorescence.emittedLight;
                flow from transmitFluorescence.collectedLight to photonOut.item1;
            }
            part embeddedPhotonCounter {
                doc
                /*
                 * Silicon-based multi-pixel photon counter fabricated onto
                 * the substrate, cooled to 77 K to reduce the dark count
                 * rate. Via wall structures prevent optical cross-talk from
                 * neighbouring readout zones.
                 *
                 * Source: p.4, right column, paragraph 4; Fig. 2B.
                 */
                attribute temp : ThermodynamicTemperatureUnit = 77 [K];
                port photonIn : ~opticalPort {
                    out item item1;
                }
                port countOut : digitalPort {
                    in item item1;
                }
                perform microwaveOperation.countPhotons;
                flow from photonIn.item1 to countPhotons.light;
                flow from countPhotons.count to countOut.item1;
            }
            part electronicsLayer {
                doc
                /*
                 * Stacked wafer layers carrying the in-vacuum converters and
                 * their filters, attached to the ion trap substrate using
                 * through-silicon via and wafer-stacking technology.
                 *
                 * Source: p.5, right column, paragraph 1.
                 */
                part fpga : fieldProgrammableGateArrays {
                    port controlIn : ~digitalPort;
                    port dacDriveOut : digitalPort;
                }
                part inVacuumDac : digitalToAnalogConverter {
                    port digitalIn : ~digitalPort {
                        out item item1;
                    }
                    port coilCurrentOut : dcBiasPort {
                        in item item1;
                    }
                    port electrodeVoltageOut : dcBiasPort {
                        in item item1;
                    }
                    perform microwaveOperation.convertToAnalogDrive;
                    flow from digitalIn.item1 to convertToAnalogDrive.command;
                    flow from convertToAnalogDrive.coilCurrent to coilCurrentOut.item1;
                    flow from convertToAnalogDrive.electrodeVoltage to electrodeVoltageOut.item1;
                }
                part rcFilter {
                    port filterIn : ~dcBiasPort {
                        out item item1;
                    }
                    port filterOut : dcBiasPort {
                        in item item1;
                    }
                    perform microwaveOperation.filterElectrodeVoltage;
                    flow from filterIn.item1 to filterElectrodeVoltage.unfiltered;
                    flow from filterElectrodeVoltage.filtered to filterOut.item1;
                }
                part electrodeDriver {
                    doc
                    /*
                     * Summing amplification circuit applying the highly
                     * stable electrode potentials, and overriding them with
                     * the fast control system during shuttling operations.
                     *
                     * Source: p.4, right column, paragraph 2.
                     */
                    port voltageIn : ~dcBiasPort {
                        out item item1;
                    }
                    port potentialOut : dcBiasPort {
                        in item item1;
                    }
                    perform microwaveOperation.applyElectrodeVoltage;
                    flow from voltageIn.item1 to applyElectrodeVoltage.electrodeIn;
                    flow from applyElectrodeVoltage.electrodePotential to potentialOut.item1;
                }
                part throughSiliconVia;
                port controlIn : ~digitalPort;
                port coilCurrentOut : dcBiasPort;
                port electrodeVoltageOut : dcBiasPort;
                flow from controlIn to fpga.controlIn;
                flow from fpga.dacDriveOut to inVacuumDac.digitalIn;
                flow from inVacuumDac.coilCurrentOut to coilCurrentOut;
                flow from inVacuumDac.electrodeVoltageOut to rcFilter.filterIn;
                flow from rcFilter.filterOut to electrodeDriver.voltageIn;
                flow from electrodeDriver.potentialOut to electrodeVoltageOut;
            }
            part controlUnit : physicalControlUnit {
                doc
                /*
                 * Determines the qubit state from the photon count.
                 *
                 * Source: p.4 right column paragraph 5; p.5 left column
                 * paragraph 1.
                 */
                port countIn : ~digitalPort {
                    out item item1;
                }
                port resultOut : digitalPort {
                    in item item1;
                }
                perform microwaveOperation.determineQubitState;
                flow from countIn.item1 to determineQubitState.measurement;
                flow from determineQubitState.result to resultOut.item1;
            }
            part microchannelCooler {
                doc
                /*
                 * Liquid nitrogen microchannel cooler integrated into the
                 * back wafer, removing the heat generated by the copper
                 * wires, rf dissipation and on-chip electronics. The coolant
                 * is cooled from 77 K to 65 K to prevent boiling inside the
                 * cooler.
                 *
                 * Source: p.5, left column, paragraphs 3 and 4.
                 */
                attribute coolantTemp : ThermodynamicTemperatureUnit = 65 [K];
                part coolantTubing;
                perform microwaveOperation.removeHeat;
            }
            part supportStructure {
                part piezoActuator;
                part diffractionGrating;
            }
            port globalMicrowaveIn : ~microwavePort;
            port rfTrapIn : ~microwavePort;
            port laserSheetIn : ~opticalPort;
            port readoutExcitationIn : ~opticalPort;
            port digitalControlIn : ~digitalPort;
            port resultOut : digitalPort;
            flow from globalMicrowaveIn to qpu.globalMicrowaveIn;
            flow from rfTrapIn to qpu.rfTrapIn;
            flow from laserSheetIn to qpu.laserSheetIn;
            flow from readoutExcitationIn to qpu.readoutExcitationIn;
            flow from digitalControlIn to electronicsLayer.controlIn;
            flow from electronicsLayer.coilCurrentOut to gradientWire.currentIn;
            flow from electronicsLayer.coilCurrentOut to localBFieldCoil.currentIn;
            flow from electronicsLayer.electrodeVoltageOut to qpu.electrodeVoltageIn;
            flow from gradientWire.gradientOut to qpu.gradientIn;
            flow from localBFieldCoil.offsetFieldOut to qpu.offsetFieldIn;
            flow from qpu.fluorescenceOut to itoElectrode.photonIn;
            flow from itoElectrode.photonOut to embeddedPhotonCounter.photonIn;
            flow from embeddedPhotonCounter.countOut to controlUnit.countIn;
            flow from controlUnit.resultOut to resultOut;
        }
        flow from globalMicrowaveIn to quantumComputerModule.globalMicrowaveIn;
        flow from rfTrapDriveIn to quantumComputerModule.rfTrapIn;
        flow from laserSheetIn to viewport.beamIn;
        flow from viewport.beamOut to quantumComputerModule.laserSheetIn;
        flow from readoutExcitationIn to readoutViewport.beamIn;
        flow from readoutViewport.beamOut to quantumComputerModule.readoutExcitationIn;
        flow from digitalControlIn to electricalFeedthrough.signalIn;
        flow from electricalFeedthrough.signalOut to quantumComputerModule.digitalControlIn;
        flow from quantumComputerModule.resultOut to photonCountOut;
    }

    part microwaveReadoutSystem : classicalReadoutSystem {

        doc
        /*
         * Readout instrumentation outside the vacuum system: the excitation
         * laser that illuminates ions in the readout zone, and the analysis
         * of the returned result.
         *
         * Source: p.5, left column, paragraph 2; p.5, right column,
         * paragraph 1.
         */

        part readoutExcitationLaser {
            port beamOut : opticalPort {
                in item item1;
            }
            perform microwaveOperation.generateReadoutExcitation;  // [p.5 LC para 2]
            flow from generateReadoutExcitation.beam to beamOut.item1;
        }
        part detectionSystem {
            port countIn : ~digitalPort {
                out item item1;
            }
            port resultOut : digitalPort;
            perform microwaveOperation.analyseResult;              // [p.5 RC para 1]
            flow from countIn.item1 to analyseResult.measurement;
        }
        part readoutControlUnit {
            port resultIn : ~digitalPort;
        }
        port readoutExcitationOut : opticalPort;
        port photonCountIn : ~digitalPort;
        flow from readoutExcitationLaser.beamOut to readoutExcitationOut;
        flow from photonCountIn to detectionSystem.countIn;
        flow from detectionSystem.resultOut to readoutControlUnit.resultIn;
    }

    flow from microwaveControlSystem.globalMicrowaveOut to vacuumChamberEnv.globalMicrowaveIn;
    flow from microwaveControlSystem.rfTrapDriveOut to vacuumChamberEnv.rfTrapDriveIn;
    flow from microwaveControlSystem.laserSheetOut to vacuumChamberEnv.laserSheetIn;
    flow from microwaveControlSystem.digitalControlOut to vacuumChamberEnv.digitalControlIn;
    flow from microwaveReadoutSystem.readoutExcitationOut to vacuumChamberEnv.readoutExcitationIn;
    flow from vacuumChamberEnv.photonCountOut to microwaveReadoutSystem.photonCountIn;
}
