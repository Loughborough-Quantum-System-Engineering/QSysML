package physicalLayerAction {
    action generateMicrowavePulses;
    action performErrorCorrection;
    action pulseAttenuation;
    action pulseFiltering;
    action cryogenicAmplification;
    action quantumInformationProcessing;
}
package logicalLayerAction {
    action logicalOperations;
}
