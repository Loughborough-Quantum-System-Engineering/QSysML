// reference
// @article{ionq2026walkingcat,
//   title={Fault-Tolerant Quantum Computing with Trapped Ions: The Walking Cat Architecture},
//   author={{IonQ}},
//   year={2026}
// }
//
// Provenance notation used in line comments:
//   [p.N LC]   = page N, left  column
//   [p.N RC]   = page N, right column
//   [Tab.XXV]  = Table XXV, operations in the micro-architecture model, p.79
// Sections modelled: XIX C "Physical implementation of the moving-qubit
// operations" (p.78 RC - p.79 RC) and XIX D "Lower-level operations" (p.80 LC).

package EQCTrappedIonInterface {

    doc
    /*
     * Electronic Qubit Control interface for a trapped ion quantum charge
     * coupled device.
     *
     * Both single-qubit and two-qubit gates are implemented using EQC, which
     * combines electronic position control of ionic qubits with spatially
     * structured RF magnetic fields generated by RF currents, rather than
     * with individually addressed laser beams. An RF signal induces rotation
     * between two hyperfine levels of an ion.
     *
     * The chip is organised into zones. Every horizontal section has a gate
     * RF antenna underneath, and those sections are the gate zones; since
     * single-qubit gates also require near-field RF they are available only
     * there. Qubit reset and readout become available when the ion is at an
     * optical zone, a section with output grating couplers for various laser
     * wavelengths and a collecting lens that relays photons to a
     * photodetector.
     *
     * A key advantage of this architecture is that a single wire for a gate
     * antenna can be routed under multiple linear sections, so a large number
     * of two-qubit gates can be performed in parallel; this extensive
     * parallelism based on simple classical control is one of the main
     * benefits of trapped ion architectures based on electronic control.
     *
     * Source: Walking Cat architecture, section XIX C, p.78 left column
     * through p.79 right column, and section XIX D, p.80 left column, with
     * Table XXV on p.79.
     */

    public import QuantumComputing::physicalLayerDefinitions::*;
    public import CommonInstruments::*;
    public import AtomicCommon::*;
    public import ISQ::*;
    public import SI::*;

    // =====================================================================
    // Action definitions
    // =====================================================================

    action def IssueControlSequence {
        doc
        /*
         * Issue the digital control sequence that schedules the gate,
         * transport, cooling and measurement operations.
         *
         * Source: Table XXV, p.79.
         */
        out item sequence : digitalData;
    }

    action def GenerateElectrodeWaveform {
        doc
        /*
         * Generate the time-dependent control waveforms applied to the
         * transport electrodes. Each shuttling step is framed as a
         * constrained optimization problem, matching the desired moving
         * potential to a linear combination of basis potentials generated
         * from the transport electrodes.
         *
         * Source: p.79, right column, transport paragraph.
         */
        in item sequence : digitalData;
        out item electrodeVoltage : dcBias;
    }

    action def GenerateGateRfSignal {
        doc
        /*
         * Generate the RF drive that produces the spatially structured
         * magnetic fields used for gates. An RF signal can induce rotation
         * between the two hyperfine levels of an ion that define a Bloch
         * sphere.
         *
         * Source: p.78, right column, one-qubit and two-qubit gates
         * paragraph.
         */
        in item sequence : digitalData;
        out item rfDrive : microwaveSignal;
    }

    action def RadiateNearFieldRf {
        doc
        /*
         * Radiate the near-field RF from the gate antenna beneath the linear
         * section. Every horizontal section has a gate RF antenna underneath,
         * and a single wire for a gate antenna can be routed under multiple
         * linear sections so that many two-qubit gates run in parallel.
         *
         * Source: p.78, left column, zonal operation paragraph.
         */
        in item rfDrive : microwaveSignal;
        out item nearField : magneticField;
    }

    action def TransportIon {
        doc
        /*
         * Move an ion by quasistatically updating the electrode voltages to
         * transition from one potential well configuration into another, so
         * that a well centred at one location adiabatically shuttles to a
         * nearby location, similar to how signal electrons are transferred in
         * CCD cameras.
         *
         * Source: p.79, right column, transport paragraph; Table XXV,
         * shuttling row.
         */
        in item electrodeVoltage : dcBias;
        attribute shuttlingTime;                    // 5 to 15 us [Tab.XXV]
    }

    action def MergeWells {
        doc
        /*
         * Merge two single-ion crystals into a two-ion crystal, forming an
         * ion crystal inside a common potential well in which the motions of
         * the ions hybridize into collective motional modes. Required before
         * a two-qubit gate, since the participating ions must be in the same
         * linear section above a gate antenna with their wells merged.
         *
         * Source: p.78, left and right columns; Table XXV, merge row.
         */
        in item electrodeVoltage : dcBias;
        attribute mergeTime;                        // 50 to 100 us [Tab.XXV]
    }

    action def SplitWells {
        doc
        /*
         * Split a merged well back into two, separating the two-ion crystal
         * after the entangling operation.
         *
         * Source: Table XXV, split row, p.79.
         */
        in item electrodeVoltage : dcBias;
        attribute splitTime;                        // 50 to 100 us [Tab.XXV]
    }

    action def PerformSingleQubitGate {
        doc
        /*
         * Implement an SU(2) rotation on a single ion. Site-selective
         * single-qubit operations are controlled by locally addressable
         * offset operations that control the interaction of individual ions
         * with the driving field, which allows massively parallel layers of
         * single-qubit gates with locally controlled addressing.
         *
         * Source: p.78, right column; Table XXV, single-qubit drives row.
         */
        in item nearField : magneticField;
        attribute gateTime;                         // 5 to 10 us [Tab.XXV]
    }

    action def PerformEntanglingGate {
        doc
        /*
         * Implement the entangling interaction on a merged two-ion crystal.
         * An RF gradient couples strongly to a particular collective mode and
         * induces the two ions to follow a state-dependent trajectory in the
         * motional phase space, so the qubits acquire a state-dependent
         * geometric phase. That trajectory must begin and end in the same
         * state so the internal state remains unentangled with the motional
         * mode.
         *
         * Perturbations to the phase space trajectory by phonons, and leakage
         * outside the qubit subspace due to off-resonant driving of unwanted
         * transitions, are the dominant sources of remaining error after
         * calibration.
         *
         * Source: p.78, right column; Table XXV, entangling drives row.
         */
        in item nearField : magneticField;
        attribute gateTime;                         // 100 to 300 us [Tab.XXV]
    }

    action def GenerateLaserBeam {
        doc
        /*
         * Produce one of the laser beams required for loading, cooling,
         * preparation, shelving or measurement.
         *
         * Source: p.78 right column; p.80 left column; Table XXV.
         */
        out item beam : opticalSignal;
    }

    action def RouteLightToZone {
        doc
        /*
         * Route laser light to an optical zone through the on-chip photonic
         * layer. An optical zone is a section with output grating couplers
         * for various laser wavelengths and a collecting lens that relays
         * photons to a photodetector.
         *
         * Optical zone density is sparser than gate zone density because of
         * the engineering challenge of photonic waveguide routing with small
         * bend radii and optical crosstalk between neighbouring optical
         * zones.
         *
         * Source: p.78, left column, zonal operation paragraph.
         */
        in item light : opticalSignal;
        out item deliveredLight : opticalSignal;
    }

    action def LoadIon {
        doc
        /*
         * Load ions into the trap. A high flux of ions is generated by
         * photo-ionizing a beam of neutral atoms produced by ablation, ovens,
         * or a magneto-optical trap. The flux is photoionized inside the
         * trapping region and laser-cooled to remove motional quanta, a
         * necessary step for high-fidelity transport and gate operation.
         *
         * Loading is fundamentally non-deterministic, so loading rates
         * generally need to be kept higher than loss rates, with a mechanism
         * for ejecting or storing excess loaded ions.
         *
         * Source: p.80, left column, loading paragraph.
         */
        in item ionisationBeam : opticalSignal;
        attribute loadingRate;                      // > 400 ions/s [p.80 LC]
    }

    action def CoolIon {
        doc
        /*
         * Remove motional entropy from the ions and dissipate it to the
         * environment through spontaneous emission. Doppler cooling is the
         * simplest and most robust method, providing a frictional cooling
         * force through velocity-dependent radiation pressure, and is used
         * for hot ions freshly captured in a well. It leaves a relatively
         * high steady-state motional entropy, so sideband, EIT or
         * polarization gradient cooling is used to approach the motional
         * ground state.
         *
         * Data qubits cannot be laser-cooled, but their motional entropies
         * can be effectively reduced by sympathetic cooling.
         *
         * Source: p.80, left column, cooling paragraph; Table XXV, cooling
         * laser pulses row.
         */
        in item coolingBeam : opticalSignal;
        attribute coolingRate;                      // 0.3 phonon/us [Tab.XXV]
        attribute steadyStatePhononNumber;          // n ~ 1 [p.80 LC]
    }

    action def PrepareState {
        doc
        /*
         * Initialize the internal state of a cooled ion by optical pumping,
         * then map it to a specific internal state that serves as one of the
         * two qubit levels. Optical pumping illuminates the ion with a laser
         * of specific wavelength and polarization so that the internal state
         * population performs a random walk through the energy level
         * manifold, as stimulated excitation followed by spontaneous
         * emission, until most of the population falls into a dark state from
         * which it cannot escape.
         *
         * Physical and engineering constraints limit the steady-state
         * population in the dark state, which is the fidelity of optical
         * pumping. Shelving pulses from laser or RF then transfer the dark
         * state population to the target qubit state, and a heralding process
         * may be used to detect failed state preparation.
         *
         * Source: p.78, right column, state preparation paragraph;
         * Table XXV, preparation laser pulses row.
         */
        in item pumpingBeam : opticalSignal;
        in item shelvingDrive : opticalSignal;
        attribute preparationTime;                  // 450 us [Tab.XXV]
        attribute postSelectionRate;                // > 90 % [Tab.XXV]
    }

    action def ShelveQubit {
        doc
        /*
         * Perform the shelving pulses that map the qubit back to a ground
         * state of the ion where it can continuously fluoresce under
         * illumination by the excitation lasers.
         *
         * Source: p.79, right column, measurement paragraph.
         */
        in item shelvingBeam : opticalSignal;
        out item shelvedState : opticalSignal;
    }

    action def CollectFluorescence {
        doc
        /*
         * Collect the fluorescent photons with collection optics focused on
         * the ions and relay them onto the photodetectors, using the
         * collecting lens of the optical zone.
         *
         * Source: p.79, right column, measurement paragraph; p.78, left
         * column, zonal operation paragraph.
         */
        in item fluorescence : opticalSignal;
        out item relayedPhotons : opticalSignal;
    }

    action def DetectPhotons {
        doc
        /*
         * Convert the relayed photons into a photon count on the
         * photodetector.
         *
         * Source: p.79, right column, measurement paragraph; Table XXV,
         * measurement laser pulses row.
         */
        in item relayedPhotons : opticalSignal;
        out item photonCount : digitalData;
        attribute exposureTime;                     // 350 us per image [Tab.XXV]
    }

    action def BinariseCount {
        doc
        /*
         * Binarize each detector signal according to whether the photon count
         * within the exposure time is below or above a threshold count. The
         * imaging procedure is applied sequentially to each of the two qubit
         * states, so the two classical bits obtained indicate whether the
         * qubit was in the first state, the second state, or neither, the
         * last indicating potential qubit leakage or loss.
         *
         * Source: p.79, right column, measurement paragraph.
         */
        in item photonCount : digitalData;
        out attribute qubitState;
        attribute thresholdCount;
    }

    // =====================================================================
    // End-to-end behaviour
    // =====================================================================
    action def EqcControlAndReadout {

        doc
        /*
         * Sequence of the EQC control and readout cycle for one gating and
         * measurement round.
         *
         * Ions are loaded, cooled and prepared at an optical zone. For a
         * two-qubit gate the ions are transported into a common linear
         * section above a gate antenna and their wells merged; the near-field
         * RF from the antenna then drives the entangling interaction, after
         * which the wells are split again. Measurement requires transporting
         * the ion to an optical zone, shelving it, illuminating it, and
         * binarizing the collected photon count.
         *
         * The ordering reflects the zonal constraint: gates are available
         * only in gate zones, reset and readout only in optical zones, so
         * transport steps separate the two.
         *
         * This definition states ordering and the action-to-action item
         * chain. The physical routing of those items through ports is
         * modelled in the parts.
         *
         * Source: p.78 left column through p.80 left column, with
         * Table XXV.
         */

        out attribute measuredQubitState;

        // ---- control generation ----
        action issueControlSequence : IssueControlSequence;        // [Tab.XXV]
        action generateElectrodeWaveform : GenerateElectrodeWaveform; // [p.79 RC]
        action generateGateRfSignal : GenerateGateRfSignal;        // [p.78 RC]
        action radiateNearFieldRf : RadiateNearFieldRf;            // [p.78 LC]

        // ---- laser generation and delivery ----
        action generateIonisationBeam : GenerateLaserBeam;         // [p.80 LC]
        action generateCoolingBeam : GenerateLaserBeam;            // [p.80 LC]
        action generatePumpingBeam : GenerateLaserBeam;            // [p.78 RC]
        action generateShelvingBeam : GenerateLaserBeam;           // [p.79 RC]
        action generateExcitationBeam : GenerateLaserBeam;         // [p.79 RC]
        action routeControlLight : RouteLightToZone;               // [p.78 LC]
        action routeReadoutLight : RouteLightToZone;               // [p.78 LC]

        // ---- ion operations ----
        action loadIon : LoadIon;                                  // [p.80 LC]
        action coolIon : CoolIon;                                  // [p.80 LC]
        action prepareState : PrepareState;                        // [p.78 RC]
        action transportToGateZone : TransportIon;                 // [p.79 RC]
        action mergeWells : MergeWells;                            // [Tab.XXV]
        action performSingleQubitGate : PerformSingleQubitGate;    // [Tab.XXV]
        action performEntanglingGate : PerformEntanglingGate;      // [Tab.XXV]
        action splitWells : SplitWells;                            // [Tab.XXV]
        action transportToOpticalZone : TransportIon;              // [p.79 RC]

        // ---- measurement ----
        action shelveQubit : ShelveQubit;                          // [p.79 RC]
        action collectFluorescence : CollectFluorescence;          // [p.79 RC]
        action detectPhotons : DetectPhotons;                      // [p.79 RC]
        action binariseCount : BinariseCount;                      // [p.79 RC]

        // ---- control nodes ----
        fork initiate;
        join joinPrepare;
        join joinGate;

        // ---- ordering ----
        first start then initiate;
        first initiate then issueControlSequence;                  // [Tab.XXV]
        first issueControlSequence then generateElectrodeWaveform; // [p.79 RC]
        first issueControlSequence then generateGateRfSignal;      // [p.78 RC]
        first generateGateRfSignal then radiateNearFieldRf;        // [p.78 LC]

        first initiate then generateIonisationBeam;                // [p.80 LC]
        first initiate then generateCoolingBeam;
        first initiate then generatePumpingBeam;
        first initiate then generateShelvingBeam;
        first initiate then generateExcitationBeam;
        first generateIonisationBeam then routeControlLight;       // [p.78 LC]
        first generateExcitationBeam then routeReadoutLight;

        // load, cool and prepare at an optical zone
        first routeControlLight then loadIon;                      // [p.80 LC]
        first loadIon then coolIon;                                // [p.80 LC]
        first coolIon then joinPrepare;
        first generatePumpingBeam then joinPrepare;
        first joinPrepare then prepareState;                       // [p.78 RC]

        // transport to a gate zone and gate
        first prepareState then transportToGateZone;               // [p.79 RC]
        first generateElectrodeWaveform then transportToGateZone;
        first transportToGateZone then mergeWells;                 // [Tab.XXV]
        first mergeWells then joinGate;
        first radiateNearFieldRf then joinGate;
        first joinGate then performSingleQubitGate;                // [Tab.XXV]
        first performSingleQubitGate then performEntanglingGate;
        first performEntanglingGate then splitWells;               // [Tab.XXV]

        // transport back to an optical zone and measure
        first splitWells then transportToOpticalZone;              // [p.79 RC]
        first transportToOpticalZone then shelveQubit;             // [p.79 RC]
        first routeReadoutLight then shelveQubit;
        first shelveQubit then collectFluorescence;
        first collectFluorescence then detectPhotons;
        first detectPhotons then binariseCount;
        first binariseCount then done;

        // ---- item chain ----
        flow from issueControlSequence.sequence to generateElectrodeWaveform.sequence;
        flow from issueControlSequence.sequence to generateGateRfSignal.sequence;
        flow from generateGateRfSignal.rfDrive to radiateNearFieldRf.rfDrive;
        flow from radiateNearFieldRf.nearField to performSingleQubitGate.nearField;
        flow from radiateNearFieldRf.nearField to performEntanglingGate.nearField;

        flow from generateElectrodeWaveform.electrodeVoltage to transportToGateZone.electrodeVoltage;
        flow from generateElectrodeWaveform.electrodeVoltage to transportToOpticalZone.electrodeVoltage;
        flow from generateElectrodeWaveform.electrodeVoltage to mergeWells.electrodeVoltage;
        flow from generateElectrodeWaveform.electrodeVoltage to splitWells.electrodeVoltage;

        flow from generateIonisationBeam.beam to routeControlLight.light;
        flow from routeControlLight.deliveredLight to loadIon.ionisationBeam;
        flow from generateCoolingBeam.beam to coolIon.coolingBeam;
        flow from generatePumpingBeam.beam to prepareState.pumpingBeam;
        flow from generateShelvingBeam.beam to prepareState.shelvingDrive;
        flow from generateShelvingBeam.beam to shelveQubit.shelvingBeam;

        flow from generateExcitationBeam.beam to routeReadoutLight.light;
        flow from routeReadoutLight.deliveredLight to shelveQubit.shelvingBeam;
        flow from shelveQubit.shelvedState to collectFluorescence.fluorescence;
        flow from collectFluorescence.relayedPhotons to detectPhotons.relayedPhotons;
        flow from detectPhotons.photonCount to binariseCount.photonCount;

        bind measuredQubitState = binariseCount.qubitState;
    }

    action eqcOperation : EqcControlAndReadout;

    // =====================================================================
    // Structure
    // =====================================================================
    part eqcControlSystem : classicalControlSystem {

        doc
        /*
         * Control instrumentation outside the vacuum system: the RF waveform
         * chain that drives the gate antennas, the converter chain that
         * drives the transport electrodes, and the laser system.
         *
         * Source: p.78 right column; p.79 right column.
         */

        part fpga : fieldProgrammableGateArrays {
            port sequenceOut : digitalPort {
                in item item1;
            }
            perform eqcOperation.issueControlSequence;             // [Tab.XXV]
            flow from issueControlSequence.sequence to sequenceOut.item1;
        }
        part dac : digitalToAnalogConverter {
            doc
            /*
             * Produces the time-dependent transport waveforms applied to the
             * electrodes.
             *
             * Source: p.79, right column, transport paragraph.
             */
            port digitalIn : ~digitalPort {
                out item item1;
            }
            port electrodeVoltageOut : dcBiasPort {
                in item item1;
            }
            perform eqcOperation.generateElectrodeWaveform;
            flow from digitalIn.item1 to generateElectrodeWaveform.sequence;
            flow from generateElectrodeWaveform.electrodeVoltage to electrodeVoltageOut.item1;
        }
        part rfWaveformGenerator : microwaveSource {
            doc
            /*
             * Generates the RF currents that produce the spatially structured
             * magnetic fields used for EQC gates.
             *
             * Source: p.78, right column.
             */
            port digitalIn : ~digitalPort {
                out item item1;
            }
            port rfOut : microwavePort {
                in item item1;
            }
            perform eqcOperation.generateGateRfSignal;
            flow from digitalIn.item1 to generateGateRfSignal.sequence;
            flow from generateGateRfSignal.rfDrive to rfOut.item1;
        }
        part laserSystem {
            doc
            /*
             * Laser sources for photoionization, cooling, optical pumping,
             * shelving and measurement.
             *
             * Source: p.78 right column; p.79 right column; p.80 left column.
             */
            part photoionisationLaser {
                port beamOut : opticalPort {
                    in item item1;
                }
                perform eqcOperation.generateIonisationBeam;
                flow from generateIonisationBeam.beam to beamOut.item1;
            }
            part coolingLaser {
                port beamOut : opticalPort {
                    in item item1;
                }
                perform eqcOperation.generateCoolingBeam;
                flow from generateCoolingBeam.beam to beamOut.item1;
            }
            part opticalPumpingLaser {
                port beamOut : opticalPort {
                    in item item1;
                }
                perform eqcOperation.generatePumpingBeam;
                flow from generatePumpingBeam.beam to beamOut.item1;
            }
            part shelvingLaser {
                port beamOut : opticalPort {
                    in item item1;
                }
                perform eqcOperation.generateShelvingBeam;
                flow from generateShelvingBeam.beam to beamOut.item1;
            }
            port controlLightOut : opticalPort;
            flow from photoionisationLaser.beamOut to controlLightOut;
            flow from coolingLaser.beamOut to controlLightOut;
            flow from opticalPumpingLaser.beamOut to controlLightOut;
            flow from shelvingLaser.beamOut to controlLightOut;
        }
        port electrodeVoltageOut : dcBiasPort;
        port gateRfOut : microwavePort;
        port controlLightOut : opticalPort;
        flow from fpga.sequenceOut to dac.digitalIn;
        flow from fpga.sequenceOut to rfWaveformGenerator.digitalIn;
        flow from dac.electrodeVoltageOut to electrodeVoltageOut;
        flow from rfWaveformGenerator.rfOut to gateRfOut;
        flow from laserSystem.controlLightOut to controlLightOut;
    }

    part vacuumChamberEnv {

        doc
        /*
         * Vacuum chamber housing the QCCD device. A QCCD is generally
         * operated at cryogenic temperature so that ion heating and loss due
         * to experimental imperfection are minimized: cryogenic temperature
         * strongly suppresses the background gas pressure that contributes to
         * ion collisions, and equally suppresses the anomalous ion heating
         * rate from electrode surfaces.
         *
         * Source: p.80, left column, qubit loss and replenishment paragraph.
         */

        attribute pressure : PressureUnit;

        port electrodeVoltageIn : ~dcBiasPort;
        port gateRfIn : ~microwavePort;
        port controlLightIn : ~opticalPort;
        port readoutLightIn : ~opticalPort;
        port fluorescenceOut : opticalPort;

        part loadingChip {
            doc
            /*
             * Loading region where the neutral atom beam is photoionized.
             * Ions can also be routed here to optically pump out of the
             * metastable state without inducing optical crosstalk on qubits
             * encoded in metastable states.
             *
             * Source: p.80 left column; p.79 right column, leakage reset
             * paragraph.
             */
            port ionisationLightIn : ~opticalPort;
        }

        part qccdChip {
            doc
            /*
             * The QCCD device. Every horizontal section has a gate RF antenna
             * underneath, making it a gate zone; optical zones, which carry
             * the output grating couplers and the collecting lens, are
             * available in every alternating row and are sparser than gate
             * zones because of the difficulty of photonic waveguide routing
             * with small bend radii and optical crosstalk between
             * neighbouring zones.
             *
             * Source: p.78, left column, zonal operation paragraph.
             */
            attribute temp : ThermodynamicTemperatureUnit;

            part qpu : QPU {
                doc
                /*
                 * The trapped ion register. Modelled as a black box so that
                 * only the classical interface is in scope; the gate, merge,
                 * split, transport and measurement operations are those
                 * tabulated in the micro-architecture model.
                 *
                 * Source: Table XXV, p.79.
                 */
                attribute redefines technology = qubitTechnology::trappedIon;
                port electrodeVoltageIn : ~dcBiasPort {
                    out item item1;
                }
                port nearFieldIn : ~magneticFieldPort {
                    out item item1;
                }
                port controlLightIn : ~opticalPort {
                    out item item1;
                }
                port readoutLightIn : ~opticalPort {
                    out item item1;
                }
                port fluorescenceOut : opticalPort {
                    in item item1;
                }
                perform eqcOperation.loadIon;
                perform eqcOperation.coolIon;
                perform eqcOperation.prepareState;
                perform eqcOperation.transportToGateZone;
                perform eqcOperation.mergeWells;
                perform eqcOperation.performSingleQubitGate;
                perform eqcOperation.performEntanglingGate;
                perform eqcOperation.splitWells;
                perform eqcOperation.transportToOpticalZone;
                perform eqcOperation.shelveQubit;
                flow from electrodeVoltageIn.item1 to transportToGateZone.electrodeVoltage;
                flow from electrodeVoltageIn.item1 to transportToOpticalZone.electrodeVoltage;
                flow from electrodeVoltageIn.item1 to mergeWells.electrodeVoltage;
                flow from electrodeVoltageIn.item1 to splitWells.electrodeVoltage;
                flow from nearFieldIn.item1 to performSingleQubitGate.nearField;
                flow from nearFieldIn.item1 to performEntanglingGate.nearField;
                flow from controlLightIn.item1 to loadIon.ionisationBeam;
                flow from controlLightIn.item1 to coolIon.coolingBeam;
                flow from controlLightIn.item1 to prepareState.pumpingBeam;
                flow from controlLightIn.item1 to prepareState.shelvingDrive;
                flow from readoutLightIn.item1 to shelveQubit.shelvingBeam;
                flow from shelveQubit.shelvedState to fluorescenceOut.item1;
            }
            part antennaLayer {
                doc
                /*
                 * Layer carrying the gate RF antennas. A single antenna wire
                 * can be routed under multiple linear sections, so a large
                 * number of two-qubit gates can be performed in parallel.
                 *
                 * Source: p.78, left column, zonal operation paragraph.
                 */
                part gateRfAntenna {
                    port feedIn : ~microwavePort {
                        out item item1;
                    }
                    port nearFieldOut : magneticFieldPort {
                        in item item1;
                    }
                    perform eqcOperation.radiateNearFieldRf;
                    flow from feedIn.item1 to radiateNearFieldRf.rfDrive;
                    flow from radiateNearFieldRf.nearField to nearFieldOut.item1;
                }
                port feedIn : ~microwavePort;
                port nearFieldOut : magneticFieldPort;
                flow from feedIn to gateRfAntenna.feedIn;
                flow from gateRfAntenna.nearFieldOut to nearFieldOut;
            }
            part photonicLayer {
                doc
                /*
                 * On-chip photonic routing delivering the control laser
                 * wavelengths to the optical zones through nanophotonic
                 * waveguides terminated by output grating couplers.
                 *
                 * Source: p.78, left column, zonal operation paragraph.
                 */
                part nanophotonicWaveguide {
                    port lightIn : ~opticalPort;
                    port lightOut : opticalPort;
                }
                part outputGratingCoupler {
                    port lightIn : ~opticalPort;
                    port beamOut : opticalPort;
                }
                port lightIn : ~opticalPort {
                    out item item1;
                }
                port beamOut : opticalPort {
                    in item item1;
                }
                perform eqcOperation.routeControlLight;
                flow from lightIn.item1 to routeControlLight.light;
                flow from routeControlLight.deliveredLight to beamOut.item1;
                flow from lightIn to nanophotonicWaveguide.lightIn;
                flow from nanophotonicWaveguide.lightOut to outputGratingCoupler.lightIn;
                flow from outputGratingCoupler.beamOut to beamOut;
            }
            part readoutPhotonicLayer {
                doc
                /*
                 * On-chip photonic routing delivering the measurement
                 * excitation wavelengths to the optical zones.
                 *
                 * Source: p.78, left column, zonal operation paragraph.
                 */
                part nanophotonicWaveguide {
                    port lightIn : ~opticalPort;
                    port lightOut : opticalPort;
                }
                part outputGratingCoupler {
                    port lightIn : ~opticalPort;
                    port beamOut : opticalPort;
                }
                port lightIn : ~opticalPort {
                    out item item1;
                }
                port beamOut : opticalPort {
                    in item item1;
                }
                perform eqcOperation.routeReadoutLight;
                flow from lightIn.item1 to routeReadoutLight.light;
                flow from routeReadoutLight.deliveredLight to beamOut.item1;
                flow from lightIn to nanophotonicWaveguide.lightIn;
                flow from nanophotonicWaveguide.lightOut to outputGratingCoupler.lightIn;
                flow from outputGratingCoupler.beamOut to beamOut;
            }
            part collectingLens {
                doc
                /*
                 * Collection optics of the optical zone, focused on the ions
                 * to collect fluorescent photons and relay them onto the
                 * photodetector.
                 *
                 * Source: p.78 left column; p.79 right column, measurement
                 * paragraph.
                 */
                port photonIn : ~opticalPort {
                    out item item1;
                }
                port photonOut : opticalPort {
                    in item item1;
                }
                perform eqcOperation.collectFluorescence;
                flow from photonIn.item1 to collectFluorescence.fluorescence;
                flow from collectFluorescence.relayedPhotons to photonOut.item1;
            }
            port electrodeVoltageIn : ~dcBiasPort;
            port gateRfIn : ~microwavePort;
            port controlLightIn : ~opticalPort;
            port readoutLightIn : ~opticalPort;
            port fluorescenceOut : opticalPort;
            flow from electrodeVoltageIn to qpu.electrodeVoltageIn;
            flow from gateRfIn to antennaLayer.feedIn;
            flow from antennaLayer.nearFieldOut to qpu.nearFieldIn;
            flow from controlLightIn to photonicLayer.lightIn;
            flow from photonicLayer.beamOut to qpu.controlLightIn;
            flow from readoutLightIn to readoutPhotonicLayer.lightIn;
            flow from readoutPhotonicLayer.beamOut to qpu.readoutLightIn;
            flow from qpu.fluorescenceOut to collectingLens.photonIn;
            flow from collectingLens.photonOut to fluorescenceOut;
        }
        flow from electrodeVoltageIn to qccdChip.electrodeVoltageIn;
        flow from gateRfIn to qccdChip.gateRfIn;
        flow from controlLightIn to qccdChip.controlLightIn;
        flow from controlLightIn to loadingChip.ionisationLightIn;
        flow from readoutLightIn to qccdChip.readoutLightIn;
        flow from qccdChip.fluorescenceOut to fluorescenceOut;
    }

    part eqcReadoutSystem : classicalReadoutSystem {

        doc
        /*
         * Measurement instrumentation: the excitation laser that illuminates
         * the shelved ion, the photodetector, and the threshold
         * discrimination that yields the classical bits.
         *
         * Source: p.79, right column, measurement paragraph.
         */

        part excitationLaser {
            port beamOut : opticalPort {
                in item item1;
            }
            perform eqcOperation.generateExcitationBeam;           // [p.79 RC]
            flow from generateExcitationBeam.beam to beamOut.item1;
        }
        part photodetector {
            port photonIn : ~opticalPort {
                out item item1;
            }
            port countOut : digitalPort {
                in item item1;
            }
            perform eqcOperation.detectPhotons;                    // [p.79 RC]
            flow from photonIn.item1 to detectPhotons.relayedPhotons;
            flow from detectPhotons.photonCount to countOut.item1;
        }
        part thresholdDiscriminator {
            doc
            /*
             * Binarizes each detector signal against a threshold count, so
             * that the two classical bits distinguish the first state, the
             * second state, or neither, the last indicating leakage or loss.
             *
             * Source: p.79, right column, measurement paragraph.
             */
            port countIn : ~digitalPort {
                out item item1;
            }
            perform eqcOperation.binariseCount;
            flow from countIn.item1 to binariseCount.photonCount;
        }
        port readoutLightOut : opticalPort;
        port fluorescenceIn : ~opticalPort;
        flow from excitationLaser.beamOut to readoutLightOut;
        flow from fluorescenceIn to photodetector.photonIn;
        flow from photodetector.countOut to thresholdDiscriminator.countIn;
    }

    flow from eqcControlSystem.electrodeVoltageOut to vacuumChamberEnv.electrodeVoltageIn;
    flow from eqcControlSystem.gateRfOut to vacuumChamberEnv.gateRfIn;
    flow from eqcControlSystem.controlLightOut to vacuumChamberEnv.controlLightIn;
    flow from eqcReadoutSystem.readoutLightOut to vacuumChamberEnv.readoutLightIn;
    flow from vacuumChamberEnv.fluorescenceOut to eqcReadoutSystem.fluorescenceIn;
}
