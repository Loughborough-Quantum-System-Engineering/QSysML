package Parameters {
    /* This package includes all defined attributes that defined as paramters in the standards */
    attribute def MeasurementBasis {
        doc /* Basis in which a quantum signal is measured (ITU-T Y.3802, 7.1 a). A value, not an item. */
    }
}
