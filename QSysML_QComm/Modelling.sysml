package Modelling {
    package LogicalqkdNetwork {
        part BB84Network {
            part qkdNode : LogicalEntities::QKDNode [1..*] {
                part qkdModule : LogicalEntities::QKDModule [1..*];
                part keyManager : LogicalEntities::KeyManger;
            }
            connection qkdLink : LinksAndPorts::QKDLink [1..*];
        }
        package quantumLayer {
            doc /* The quantum layer generates QKD-keys between pairs of QKD modules over QKD links, and supplies them to the key management layer. */
        }
        package keyManagementLayer {
            doc
            /* Its job, per Y.3802, is to receive and manage keys generated by QKD modules and QKD links, 
             * relay the keys, and supply the keys to cryptographic applications. */
        }
        package QKDNcontrolLayer;
        package QKDNmanagementLayer;
    }
    package PhysicalqkdNetwork;
}
view map : DS_Views::SymbolicViews::gv {
    expose Modelling::LogicalqkdNetwork;
}
